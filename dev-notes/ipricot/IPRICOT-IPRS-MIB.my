IPRICOT-IPRS-MIB DEFINITIONS ::= BEGIN

IMPORTS
	internet, directory, mgmt,
        experimental, private, enterprises,
        ObjectName, ObjectSyntax, SimpleSyntax,
        ApplicationSyntax, NetworkAddress, IpAddress,
        Counter, Gauge, TimeTicks, Opaque
		FROM RFC1155-SMI
	OBJECT-TYPE
		FROM RFC-1212;

 -- tree structure
--ipricot MODULE-IDENTITY
--    LAST-UPDATED "200112170000Z"
--    ORGANIZATION "IPricot SA (formerly Dotcom)"
--    CONTACT-INFO "IPricot private enterprise MIB definition"
--    DESCRIPTION
--	  "This file defines the private IPricot SNMP MIB extensions."
--    ::= { enterprises 6697 }

--IPricot		OBJECT IDENTIFIER ::= { enterprises 6697 }


IPricot         OBJECT IDENTIFIER ::= { enterprises 6697 }

products	OBJECT IDENTIFIER ::= { IPricot 1 }
iprs1x00	OBJECT IDENTIFIER ::= { products 1 }

iprMIBObjects     OBJECT IDENTIFIER ::= { iprs1x00 1 }
iprMIBConformance OBJECT IDENTIFIER  ::= { iprs1x00 2 }

--
-- Trap definitions
--

-- Generic traps [0..5]

coldStart TRAP-TYPE
    ENTERPRISE  IPricot
    DESCRIPTION
                "A coldStart trap signifies that the agent of the
                 receiver is initializing itself."
    ::= 0

-- Specific traps

iprs1x00SpecTrapPrefix OBJECT IDENTIFIER ::= { iprs1x00 3 }
downStreamTrap OBJECT IDENTIFIER ::= { iprs1x00SpecTrapPrefix 1 }

downStreamUnlock TRAP-TYPE
    ENTERPRISE  downStreamTrap
    DESCRIPTION
                "A downStreamUnLock trap signifies that the downstream
                demodulator card breaks lock.
                The trap is sent every 5 seconds while the signal is
		not locked again."
    ::= 0


--
-- Satellite variables
--

downStream      OBJECT IDENTIFIER ::= { iprMIBObjects 1 }

lowbandInf	OBJECT-TYPE
	SYNTAX        Integer32
        ACCESS        read-write
        STATUS        mandatory
        DESCRIPTION   "Inferior bound of low band. unit:da.Hz (deca-hertz).
                       120000000 means 1.2 GHz"
        ::= { downStream 1 }

lowbandSup	OBJECT-TYPE
	SYNTAX        Integer32
        ACCESS        read-write
        STATUS        mandatory
        DESCRIPTION   "Superior bound of low band. unit:da.Hz (deca-hertz).
                       120000000 means 1.2 GHz"
        ::= { downStream 2 }

lowbandOffset	OBJECT-TYPE
	SYNTAX        Integer32
        ACCESS        read-write
        STATUS        mandatory
        DESCRIPTION   "Local oscillator of low band. unit:da.Hz (deca-hertz).
                       120000000 means 1.2 GHz"
        ::= { downStream 3 }

hibandInf	OBJECT-TYPE
	SYNTAX        Integer32
        ACCESS        read-write
        STATUS        mandatory
        DESCRIPTION   "Inferior bound of high band. unit:da.Hz (deca-hertz).
                       120000000 means 1.2 GHz"
        ::= { downStream 4 }

hibandSup	OBJECT-TYPE
	SYNTAX        Integer32
        ACCESS        read-write
        STATUS        mandatory
        DESCRIPTION   "Superior bound of high band. unit:da.Hz (deca-hertz).
                       120000000 means 1.2 GHz"
        ::= { downStream 5 }

hibandOffset	OBJECT-TYPE
	SYNTAX        Integer32
        ACCESS        read-write
        STATUS        mandatory
        DESCRIPTION   "Local oscillator of high band. unit:da.Hz (deca-hertz).
                       120000000 means 1.2 GHz"
        ::= { downStream 6 }

freq OBJECT-TYPE
	SYNTAX        Integer32
        ACCESS        read-write
        STATUS        mandatory
        DESCRIPTION   "Receiving frequency. unit:da.Hz (deca-hertz).
                       120000000 means 1.2 GHz"
        ::= { downStream 7 }

tunedFreq	OBJECT-TYPE
	SYNTAX        Integer32
        ACCESS        read-only
        STATUS        mandatory
        DESCRIPTION   "Frequency after correction. unit:da.Hz (deca-hertz).
                       120000000 means 1.2 GHz"
        ::= { downStream 8 }

tuneFreq	OBJECT-TYPE
	SYNTAX        Integer32 { no(0), yes(1) }
        ACCESS        read-write
        STATUS        mandatory
        DESCRIPTION   "Do or don't frequency correction."
        ::= { downStream 9 }

bauds OBJECT-TYPE
	SYNTAX        Integer32
        ACCESS        read-write
        STATUS        mandatory
        DESCRIPTION   "Baud rate. unit:bauds"
        ::= { downStream 10 }

fec OBJECT-TYPE
	SYNTAX        Integer32 {
		aHalf(0),
		twoThirds(1),
		threeQuarter(2),
		fourFifth(3),
		fiveSixth(4),
		sixSeventh(5),
		sevenEighth(6),
		eightNinth(7),
		fecAuto(8) }
        ACCESS        read-write
        STATUS        mandatory
        DESCRIPTION   "Forward Error Code"
        ::= { downStream 11 }

polar	OBJECT-TYPE
	SYNTAX        Integer32 {
		      horizontalLHCP18v(0),
		      verticalRHCP14v(1) }
        ACCESS        read-write
        STATUS        mandatory
        DESCRIPTION   "Polarization"
        ::= { downStream 12 }

lnb	OBJECT-TYPE
	SYNTAX        Integer32 { no(0), yes(1) }
        ACCESS        read-write
        STATUS        mandatory
        DESCRIPTION   "LNB power"
        ::= { downStream 13 }

mod	OBJECT-TYPE
	SYNTAX        Integer32 {
		qpsk(0),
		eightPSK(1),
		sixteenQAM(2) }
        ACCESS        read-only
        STATUS        mandatory
        DESCRIPTION   "Type of modulation"
        ::= { downStream 14 }


--
-- "PID MPE"
--
mpePidsTable OBJECT-TYPE
	SYNTAX SEQUENCE OF MpePidsEntry
	MAX-ACCESS	not-accessible
        STATUS        mandatory
        DESCRIPTION   "List of MPE PIDs currently filtered"
        ::= { downStream 15 }

mpePidsEntry  OBJECT-TYPE
    SYNTAX     MpePidsEntry
    MAX-ACCESS not-accessible
    STATUS     current
    DESCRIPTION "A MPE PID entry"
    INDEX      { mpePidsIndex }
    ::= { mpePidsTable  1 }

MpePidsEntry ::= SEQUENCE {
	mpePidsIndex	Integer32,
	mpePidsValue	Integer32 
	}

mpePidsIndex OBJECT-TYPE
    SYNTAX	Integer32 (0..65535)
    MAX-ACCESS	read-only
    STATUS	current
    DESCRIPTION
	"Integer reference number (row number) for the mpe pid mib."
    ::= { mpePidsEntry 1 }

mpePidsValue	OBJECT-TYPE
    SYNTAX	Integer32 (0..8191)
    MAX-ACCESS	read-only
    STATUS	current
    DESCRIPTION
	"PID MPE for the mpe pid mib."
    ::= { mpePidsEntry 2 }

--
-- fin "PID MPE"
--

crcMPE OBJECT-TYPE
	SYNTAX        Integer32 {
		no(0),
		yes(1) }
        ACCESS        read-write
        STATUS        mandatory
        DESCRIPTION   "Do or don't process CRC in MPE header."
        ::= { downStream 16 }

vber  OBJECT-TYPE
	SYNTAX        OCTET STRING
        ACCESS        read-only
        STATUS        mandatory
        DESCRIPTION   "Viterbi Bit Error Rate."
        ::= { downStream 17 }

ebn  OBJECT-TYPE
	SYNTAX        Integer32
        ACCESS        read-only
        STATUS        mandatory
        DESCRIPTION   "Eb/N. unit:d.dB (deci-decibel) 100 means 10.0 dB"
        ::= { downStream 18 }

digitalLevel  OBJECT-TYPE
	SYNTAX        Integer32 (0..100)
        ACCESS        read-only
        STATUS        mandatory
        DESCRIPTION   "Digital Level percentage."
        ::= { downStream 19 }

lnbVoltage  OBJECT-TYPE
	SYNTAX        Integer32
        ACCESS        read-only
        STATUS        mandatory
        DESCRIPTION   "LNB voltage unit:h.V (hecto volts)
                       1419 means 14.19 volts"
        ::= { downStream 20 }

lockStatus  OBJECT-TYPE
	SYNTAX        Integer32 {
			unlock(0),
			lock(1) }
        ACCESS        read-only
        STATUS        mandatory
        DESCRIPTION   "Demodulator lock status."
        ::= { downStream 21 }


uncorrectablePackets OBJECT-TYPE
	SYNTAX        Integer32 (0..127)
        ACCESS        read-only
        STATUS        mandatory
        DESCRIPTION   "Number of uncorrectable packets after FEC."
        ::= { downStream 22 }


llcSnapTraffic OBJECT-TYPE
   SYNTAX      Integer32 {
                  discard(0),
                  snap802dot1(1),
                  snap802dot2(2),
                  snap802dot1and802dot2(3) }
   ACCESS        read-only
   STATUS        mandatory
   DESCRIPTION   "LLC Snap Traffic."
   ::= {downStream 23 }                

macFilteringBytes OBJECT-TYPE
   SYNTAX         Integer32 (0..6)
   ACCESS         read-only
   STATUS         mandatory
   DESCRIPTION    "Number of bytes used for MAC Address filtering."
   ::= {downStream 24 }
       
ipCopyPrefix1 OBJECT-TYPE
   SYNTAX         OCTET STRING (SIZE (1))
   ACCESS         read-only
   STATUS         mandatory
   DESCRIPTION    "The first byte for the MAC address filtering."
   ::= {downStream 25 }

ipCopyPrefix2 OBJECT-TYPE
   SYNTAX         OCTET STRING (SIZE (1))
   ACCESS         read-only
   STATUS         mandatory
   DESCRIPTION    "The second byte for the MAC address filtering."
   ::= {downStream 26 }

ipCopyTable OBJECT-TYPE
	SYNTAX SEQUENCE OF IpCopyEntry
	MAX-ACCESS	not-accessible
   STATUS        mandatory
   DESCRIPTION   
   "List of ip copy addresses suffixes = last four bytes used for 
   MAC address filtering."
   ::= { downStream 27 }

ipCopyEntry  OBJECT-TYPE
    SYNTAX     IpCopyEntry
    MAX-ACCESS not-accessible
    STATUS     current
    DESCRIPTION "A ip copy suffix entry"
    INDEX      { ipCopyIndex }
    ::= { ipCopyTable  1 }

IpCopyEntry ::= SEQUENCE {
	ipCopyIndex	Integer32,
	ipCopyValue	OCTET STRING (SIZE (4)) 
	}

ipCopyIndex OBJECT-TYPE
    SYNTAX	Integer32 (0..65535)
    MAX-ACCESS	read-only
    STATUS	current
    DESCRIPTION
	"Integer reference number (row number) for the ip copy mib."
    ::= { ipCopyEntry 1 }

ipCopyValue	OBJECT-TYPE
    SYNTAX	OCTET STRING (SIZE (4))
    MAX-ACCESS	read-only
    STATUS	current
    DESCRIPTION
	"The last four bytes of the MAC address used for MAC address filtering."
    ::= { ipCopyEntry 2 }

delayBetweenLockAttempts OBJECT-TYPE
    SYNTAX       Integer32
    ACCESS       read-only
    STATUS       mandatory
    DESCRIPTION  "Delay in seconds between lock attempts."
    ::= {downStream 28 }

scanningFrequency OBJECT-TYPE
    SYNTAX       Integer32 { no(0), yes(1) }
    ACCESS       read-only
    STATUS       mandatory
    DESCRIPTION  "Scanning Frequency."
    ::= {downStream 29 }

scanningStep OBJECT-TYPE
    SYNTAX       Integer32
    ACCESS       read-only
    STATUS       mandatory
    DESCRIPTION  "Scanning Frequency Step (in KHz)."
    ::= {downStream 30 }

minScanningFreqPerStep OBJECT-TYPE
    SYNTAX       Integer32
    ACCESS       read-only
    STATUS       mandatory
    DESCRIPTION  "Minimum Scanning Frequency per Step (in seconds)."
    ::= {downStream 31 }

maxScanningFreqPerStep OBJECT-TYPE
    SYNTAX       Integer32
    ACCESS       read-only
    STATUS       mandatory
    DESCRIPTION  "Maximum Scanning Frequency per Step (in seconds)."
    ::= {downStream 32 }

delayBeforeScan OBJECT-TYPE
    SYNTAX       Integer32
    ACCESS       read-only
    STATUS       mandatory
    DESCRIPTION  "Delay before scan (in seconds)."
    ::= {downStream 33 }

scanningRange OBJECT-TYPE
    SYNTAX       Integer32
    ACCESS       read-only
    STATUS       mandatory
    DESCRIPTION  "Scanning Range (in KHz)."
    ::= {downStream 34 }


--
-- Base entries
--
base      OBJECT IDENTIFIER ::= { iprMIBObjects 2 }

temperature OBJECT-TYPE
	SYNTAX        Integer32 
        ACCESS        read-only
        STATUS        mandatory
        DESCRIPTION   "Inside temperature. unit:h.°C (hecto celsius degree)
                       5269 means 52.69°C"
        ::= { base 1 }

temperatureTuner OBJECT-TYPE
	SYNTAX        Integer32 
        ACCESS        read-only
        STATUS        mandatory
        DESCRIPTION   "Inside temperature, near tuner. unit:h.°C 
                       (hecto celsius degree)
                       5269 means 52.69°C"
        ::= { base 2 }

distributionVersion OBJECT-TYPE
	SYNTAX        OCTET STRING
        ACCESS        read-only
        STATUS        mandatory
        DESCRIPTION   "IPricot software distribution reference."
        ::= { base 3  }

serialNumber  OBJECT-TYPE
	SYNTAX        OCTET STRING
        ACCESS        read-only
        STATUS        mandatory
        DESCRIPTION   "IPricot serial number for this device."
        ::= { base 4 }

END
